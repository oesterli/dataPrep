FME workspace 220808_BH_2_CesiumTiles_070622_pipereplacer_ama.fmw

Parameters:
- BH_Diameter =
- BH_ID =
- DestDataset_CESIUM3DTILES =
- DestDataset_CSV2_4 =
- DestDataset_OBJ =
- DestDataset_XLSXW =
- LayerID_select =
- SourceDataset_CSV2 =
- SourceDataset_XLSXR =
- SourceDataset_XLSXR_7 =

Readers:
- CSV2_1: CSV2 from $(SourceDataset_CSV2)
- XLSXR_1: XLSXR from $(SourceDataset_XLSXR)
- XLSXR_2: XLSXR from $(SourceDataset_XLSXR_7)

Writers:
- CESIUM3DTILES_1: CESIUM3DTILES to $(DestDataset_CESIUM3DTILES) in EPSG:4326
- OBJ_1: OBJ to $(DestDataset_OBJ)
- XLSXW_1: XLSXW to $(DestDataset_XLSXW)
- CSV2_3: CSV2 to $(DestDataset_CSV2_4)

Export (reader XLSXR_2)
    attributes: LONGNAME char(255), ZCOORDE char(255), SHORTNAME char(255), PROJEKTNAM char(255), ORIGNAME char(255), BOHRTYP char(255), NAMEPUB char(255), QCCOORDEN char(255), QCELEVATIZ char(255), TIEFEMD char(255), QCTIEFE char(255), BOHREDAT char(255), LAND char(255), KANTON char(255), GEMEINDE char(255), STRASSE char(255), RESTRICTIO char(255), RESTRICDAT char(255), BMETHOD char(255), BOHRGUT char(255), BOHRZWECK char(255), STATUSBOHR char(255), TOPBEDROCK char(255), QCTOPBED char(255), GROUNDWATE char(255), DIAMETER char(255), INKLINAT char(255), RICHTUNG char(255), QCINKRICHT char(255), LITTOPBED char(255),
      STRATOPDEB char(255), CHROTOPBED char(255), EPSG char(255), HRS char(255), ARTANSATZZ char(255), LANDNUTZNG char(255), BEARBSTATU char(255), GEOLDATBED char(255), ATTRIBEARB char(255), ANZSCHICHT char(255), BEMERKUNG char(255), FEHLER char(255), LETZTBEARB char(255), BEARBDATUM char(255), GEODINGUID_STGENER char(255), INTV char(255), INTART char(255), GRUND char(255), QCBOHRUNG char(255), LETZTBEARB_1 char(255), BEARBDATUM_1 char(255), BAUGRDKLAS char(255), GEODINGUID_STLYRTIT char(255), DEPTHFROM char(255), DEPTHTO char(255), LAYERDESC char(255), DESCRIPTIO char(255), BESCHRSTAN char(255), QCBESCHR char(255), LITHOLOGY char(255),
      LITHOSTRAT char(255), CHRONOSTR char(255), TECTO char(255), COLOUR char(255), HUMIDITY char(255), PLASTICITY char(255), CONSISTENC char(255), COMPACTNES char(255), SOILSTATE char(255), ALTERATION char(255), GRADUATION char(255), ORGANICOMP char(255), STRIAE char(255), GRAINSIZE1 char(255), GRAINSHAPE char(255), GRAINSIZE2 char(255), COHESION char(255), USCS1 char(255), USCS2 char(255), USCS3 char(255), USCSBEST char(255), GROBBESTAN char(255), LITPETGROB char(255), CLASSDESOL char(255), PROCESSOR char(255), DATEPRO char(255), KORNRUNDU char(255), BOHRENDTIE char(255), LITHOK char(255), KIROST char(255),
      ADDPROPS char(255), KLUEFTUNG char(255), USCSORIGIN char(255), INTART_1 char(255), INTKLASSE char(255), COMMENTARY char(255), ORIGGEOL char(255), LAGEOQID char(255), LETZTBEARB_2 char(255), BEARBDATUM_2 char(255), GEODINGUID_STLAYER char(255), XCOORD char(255), YCOORD char(255), ZCOORDB char(255)
    -> ListBuilder
Note: Export Swissforage
CSV (reader CSV2_1)
    attributes: id uint32, Originalname varchar(74), Projektname varchar(251), Name öffentlich varchar(74), Bohrtyp date, Restriktion date, Restriktion Datum varchar(11), Koordinate E real64, Koordinate N real64, SRS date, QC Koordinaten date, Ansatzhöhe Z [müM] real32, HRS date, QC Ansatz Z date, Landnutzung date, Kanton varchar(13), Gemeinde varchar(24), Strasse varchar(30), Bohrmethode date, Bohrende Datum varchar(11), Bohrgut date, Bohrzweck date, Bohrduchmesser real32, Status Bohrloch date, Inklination real32, Einfallsrichtung real32, QC Inc/Richtung uint32, Tiefe (MD) [m] real32, QC Tiefe date, Top Fels [m] real32,
      QC Top Fels date, Grundwasser varchar(6), stratigraphy_id uint32, stratigraphy_name varchar(44), depth_from real32, depth_to real32, description varchar(12806), geology varchar(254), qt_description uint32, lithology real64, lithostratigraphy real64, chronostratigraphy date, tectonic_unit varchar(1), symbol varchar(1), color varchar(63), plasticity date, humidity date, consistance date, alteration date, compactness date, jointing varchar(1), soil_state date, organic_component real64, striae varchar(6), grain_size_1 date, grain_size_2 date, grain_shape varchar(1), grain_granularity varchar(27), further_properties date, uscs_1 date,
      uscs_2 date, uscs_3 varchar(1), uscs_original varchar(1), uscs_determination date, unconrocks varchar(1), debris uint32, lit_pet_deb varchar(1), lithok varchar(1), kirost varchar(1), notes varchar(9782), Eindeutige ID varchar(1), CH varchar(1), InfoGeol varchar(1), Original ID varchar(1), geoquat varchar(1), geomol varchar(1), geotherm varchar(1), kantons ID varchar(1), test varchar(1)
    -> Sorter
    -> Tester [off]
    -> AttributeRenamer
AttributeRenamer
    ATTR_TABLE:
      RENAME_SET_DEFAULT id > SHORTNAME
      RENAME_SET_DEFAULT Originalname > ORIGNAME
      RENAME_SET_DEFAULT Projektname > PROJEKTNAM
      RENAME_SET_DEFAULT Name öffentlich > NAMEPUB
      RENAME_SET_DEFAULT Bohrtyp > BOHRTYP
      RENAME_SET_DEFAULT Restriktion > RESTRICTIO
      RENAME_SET_DEFAULT Restriktion Datum > RESTRICDAT
      RENAME_SET_DEFAULT Koordinate E > XCOORD
      RENAME_SET_DEFAULT Koordinate N > YCOORD
      RENAME_SET_DEFAULT QC Koordinaten > QCCOORDEN
      RENAME_SET_DEFAULT QC Ansatz Z > QCELEVATIZ
      RENAME_SET_DEFAULT Landnutzung > LANDNUTZNG
      RENAME_SET_DEFAULT Kanton > KANTON
      RENAME_SET_DEFAULT Gemeinde > GEMEINDE
      RENAME_SET_DEFAULT Strasse > STRASSE
      RENAME_SET_DEFAULT Bohrmethode > BMETHOD
      RENAME_SET_DEFAULT Bohrende Datum > BOHREDAT
      RENAME_SET_DEFAULT Bohrgut > BOHRGUT
      RENAME_SET_DEFAULT Bohrzweck > BOHRZWECK
      RENAME_SET_DEFAULT Bohrduchmesser > DIAMETER
      RENAME_SET_DEFAULT Status Bohrloch > STATUSBOHR
      RENAME_SET_DEFAULT Inklination > INKLINAT
      RENAME_SET_DEFAULT Einfallsrichtung > RICHTUNG
      RENAME_SET_DEFAULT SRS > EPSG
      RENAME_SET_DEFAULT QC Inc/Richtung > QCINKRICHT
      RENAME_SET_DEFAULT Tiefe (MD) [m] > TIEFEMD
      RENAME_SET_DEFAULT QC Tiefe > QCTIEFE
      RENAME_SET_DEFAULT Top Fels [m] > TOPBEDROCK
      RENAME_SET_DEFAULT Grundwasser > GROUNDWATE
      RENAME_SET_DEFAULT depth_from > DEPTHFROM
      RENAME_SET_DEFAULT depth_to > DEPTHTO
      RENAME_SET_DEFAULT description > DESCRIPTIO
      RENAME_SET_DEFAULT geology > ORIGGEOL
      RENAME_SET_DEFAULT qt_description > QCBESCHR
      RENAME_SET_DEFAULT lithology > LITHOLOGY
      RENAME_SET_DEFAULT lithostratigraphy > LITHOSTRAT
      RENAME_SET_DEFAULT chronostratigraphy > CHRONOSTR
      RENAME_SET_DEFAULT tectonic_unit > TECTO
      RENAME_SET_DEFAULT color > COLOUR
      RENAME_SET_DEFAULT plasticity > PLASTICITY
      RENAME_SET_DEFAULT humidity > HUMIDITY
      RENAME_SET_DEFAULT consistance > CONSISTENC
      RENAME_SET_DEFAULT alteration > ALTERATION
      RENAME_SET_DEFAULT compactness > COMPACTNES
      RENAME_SET_DEFAULT soil_state > SOILSTATE
      RENAME_SET_DEFAULT organic_component > ORGANICOMP
      RENAME_SET_DEFAULT striae > STRIAE
      RENAME_SET_DEFAULT grain_size_1 > GRAINSIZE1
      RENAME_SET_DEFAULT grain_size_2 > GRAINSIZE2
      RENAME_SET_DEFAULT grain_shape > GRAINSHAPE
      RENAME_SET_DEFAULT further_properties > ADDPROPS
      RENAME_SET_DEFAULT grain_granularity > KORNRUNDU
      RENAME_SET_DEFAULT jointing > KLUEFTUNG
      RENAME_SET_DEFAULT uscs_1 > USCS1
      RENAME_SET_DEFAULT uscs_2 > USCS2
      RENAME_SET_DEFAULT uscs_3 > USCS3
      RENAME_SET_DEFAULT uscs_original > USCSORIGIN
      RENAME_SET_DEFAULT uscs_determination > USCSBEST
      RENAME_SET_DEFAULT lit_pet_deb > LITPETGROB
      RENAME_SET_DEFAULT lithok > LITHOK
      RENAME_SET_DEFAULT kirost > KIROST
      RENAME_SET_DEFAULT notes > COMMENTARY
      RENAME_SET_DEFAULT Ansatzhöhe Z [müM] > ZCOORDB
    MISSING_INPUT_ATTRS = REMOVE
    -> StringConcatenator
StringConcatenator
    ACTION = Overwrite Existing Attributes
    ATTRLIST = SHORTNAME
    PARM_LINE = fme_basicstring:3%17:SF-@Value(SHORTNAME)
    -> ListBuilder
ListBuilder
    GROUP_BY = ADDPROPS ALTERATION ANZSCHICHT ARTANSATZZ ATTRIBEARB BAUGRDKLAS BEARBDATUM BEARBDATUM_1 BEARBDATUM_2 BEARBSTATU BEMERKUNG BESCHRSTAN BMETHOD BOHREDAT BOHRENDTIE BOHRGUT BOHRTYP BOHRZWECK CH CHRONOSTR CHROTOPBED CLASSDESOL COHESION COLOUR COMMENTARY COMPACTNES CONSISTENC DATEPRO debris DEPTHFROM DEPTHTO DESCRIPTIO DIAMETER "Eindeutige ID" EPSG FEHLER fme_feature_type GEMEINDE GEODINGUID_STGENER GEODINGUID_STLAYER GEODINGUID_STLYRTIT GEOLDATBED geomol geoquat geotherm GRADUATION GRAINSHAPE GRAINSIZE1 GRAINSIZE2 GROBBESTAN GROUNDWATE GRUND HRS HUMIDITY InfoGeol INKLINAT INTART INTART_1 INTKLASSE INTV KANTON "kantons ID" KIROST KLUEFTUNG KORNRUNDU LAGEOQID LAND LANDNUTZNG LAYERDESC LETZTBEARB LETZTBEARB_1 LETZTBEARB_2 LITHOK LITHOLOGY LITHOSTRAT LITPETGROB LITTOPBED LONGNAME NAMEPUB ORGANICOMP ORIGGEOL "Original ID" ORIGNAME PLASTICITY PROCESSOR PROJEKTNAM "QC Top Fels" QCBESCHR QCBOHRUNG QCCOORDEN QCELEVATIZ QCINKRICHT QCTIEFE QCTOPBED RESTRICDAT RESTRICTIO RICHTUNG SHORTNAME SOILSTATE STATUSBOHR STRASSE stratigraphy_id stratigraphy_name STRATOPDEB STRIAE symbol TECTO test TIEFEMD TOPBEDROCK unconrocks USCS1 USCS2 USCS3 USCSBEST USCSORIGIN XCOORD YCOORD ZCOORDB ZCOORDE
    LIST_NAME = _list
    -> Sorter_3
Sorter_3
    SORT_PARM = DEPTHFROM NATURAL ASCENDING SHORTNAME NATURAL ASCENDING
    SORTED -> StringReplacer
    SORTED -> bh_raw (writer XLSXW_1)
bh_raw (writer XLSXW_1)
    attributes: ADDPROPS string(255), ALTERATION string(255), ANZSCHICHT string(255), ARTANSATZZ string(255), ATTRIBEARB string(255), BAUGRDKLAS string(255), BEARBDATUM string(255), BEARBDATUM_1 string(255), BEARBDATUM_2 string(255), BEARBSTATU string(255), BEMERKUNG string(255), BESCHRSTAN string(255), BMETHOD string(255), BOHREDAT string(255), BOHRENDTIE string(255), BOHRGUT string(255), BOHRTYP string(255), BOHRZWECK string(255), CHRONOSTR string(255), CHROTOPBED string(255), CLASSDESOL string(255), COHESION string(255), COLOUR string(255), COMMENTARY string(255), COMPACTNES string(255), CONSISTENC string(255), DATEPRO string(255), DEPTHFROM string(255), DEPTHTO string(255), DESCRIPTIO string(255),
      DIAMETER string(255), EPSG string(255), FEHLER string(255), GEMEINDE string(255), GEODINGUID_STGENER string(255), GEODINGUID_STLAYER string(255), GEODINGUID_STLYRTIT string(255), GEOLDATBED string(255), GRADUATION string(255), GRAINSHAPE string(255), GRAINSIZE1 string(255), GRAINSIZE2 string(255), GROBBESTAN string(255), GROUNDWATE string(255), GRUND string(255), HRS string(255), HUMIDITY string(255), INKLINAT string(255), INTART string(255), INTART_1 string(255), INTKLASSE string(255), INTV string(255), KANTON string(255), KIROST string(255), KLUEFTUNG string(255), KORNRUNDU string(255), LAGEOQID string(255), LAND string(255), LANDNUTZNG string(255), LAYERDESC string(255),
      LETZTBEARB string(255), LETZTBEARB_1 string(255), LETZTBEARB_2 string(255), LITHOK string(255), LITHOLOGY string(255), LITHOSTRAT string(255), LITPETGROB string(255), LITTOPBED string(255), LONGNAME string(255), NAMEPUB string(255), ORGANICOMP string(255), ORIGGEOL string(255), ORIGNAME string(255), PLASTICITY string(255), PROCESSOR string(255), PROJEKTNAM string(255), QCBESCHR string(255), QCBOHRUNG string(255), QCCOORDEN string(255), QCELEVATIZ string(255), QCINKRICHT string(255), QCTIEFE string(255), QCTOPBED string(255), RESTRICDAT string(255), RESTRICTIO string(255), RICHTUNG string(255), SHORTNAME string(255), SOILSTATE string(255), STATUSBOHR string(255), STRASSE string(255),
      STRATOPDEB string(255), STRIAE string(255), TECTO string(255), TIEFEMD string(255), TOPBEDROCK string(255), USCS1 string(255), USCS2 string(255), USCS3 string(255), USCSBEST string(255), USCSORIGIN string(255), XCOORD string(255), YCOORD string(255), ZCOORDB string(255), ZCOORDE string(255)
StringReplacer
    CASE = NO
    FIND_TEXT = |
    NO_MATCH = _FME_NO_OP_
    REGEXP = NO
    REPLACE_TEXT = ;
    SRC_ATTRS = ADDPROPS,ALTERATION,ANZSCHICHT,ARTANSATZZ,ATTRIBEARB,BAUGRDKLAS,BEARBDATUM,BEARBDATUM_1,BEARBDATUM_2,BEARBSTATU,BEMERKUNG,BESCHRSTAN,BMETHOD,BOHREDAT,BOHRENDTIE,BOHRGUT,BOHRTYP,BOHRZWECK,CH,CHRONOSTR,CHROTOPBED,CLASSDESOL,COHESION,COLOUR,COMMENTARY,COMPACTNES,CONSISTENC,DATEPRO,DEPTHFROM,DEPTHTO,DESCRIPTIO,DIAMETER,EPSG,Eindeutige ID,FEHLER,GEMEINDE,GEODINGUID_STGENER,GEODINGUID_STLAYER,GEODINGUID_STLYRTIT,GEOLDATBED,GRADUATION,GRAINSHAPE,GRAINSIZE1,GRAINSIZE2,GROBBESTAN,GROUNDWATE,GRUND,HRS,HUMIDITY,INKLINAT,INTART,INTART_1,INTKLASSE,INTV,InfoGeol,KANTON,KIROST,KLUEFTUNG,KORNRUNDU,LAGEOQID,LAND,LANDNUTZNG,LAYERDESC,LETZTBEARB,LETZTBEARB_1,LETZTBEARB_2,LITHOK,LITHOLOGY,LITHOSTRAT,LITPETGROB,LITTOPBED,LONGNAME,NAMEPUB,ORGANICOMP,ORIGGEOL,ORIGNAME,Original ID,PLASTICITY,PROCESSOR,PROJEKTNAM,QC Top Fels,QCBESCHR,QCBOHRUNG,QCCOORDEN,QCELEVATIZ,QCINKRICHT,QCTIEFE,QCTOPBED,RESTRICDAT,RESTRICTIO,RICHTUNG,SHORTNAME,SOILSTATE,STATUSBOHR,STRASSE,STRATOPDEB,STRIAE,TECTO,TIEFEMD,TOPBEDROCK,USCS1,USCS2,USCS3,USCSBEST,USCSORIGIN,XCOORD,YCOORD,ZCOORDB,ZCOORDE,_list{0}.ADDPROPS,_list{0}.ALTERATION,_list{0}.ANZSCHICHT,_list{0}.ARTANSATZZ,_list{0}.ATTRIBEARB,_list{0}.BAUGRDKLAS,_list{0}.BEARBDATUM,_list{0}.BEARBDATUM_1,_list{0}.BEARBDATUM_2,_list{0}.BEARBSTATU,_list{0}.BEMERKUNG,_list{0}.BESCHRSTAN,_list{0}.BMETHOD,_list{0}.BOHREDAT,_list{0}.BOHRENDTIE,_list{0}.BOHRGUT,_list{0}.BOHRTYP,_list{0}.BOHRZWECK,_list{0}.CH,_list{0}.CHRONOSTR,_list{0}.CHROTOPBED,_list{0}.CLASSDESOL,_list{0}.COHESION,_list{0}.COLOUR,_list{0}.COMMENTARY,_list{0}.COMPACTNES,_list{0}.CONSISTENC,_list{0}.DATEPRO,_list{0}.DEPTHFROM,_list{0}.DEPTHTO,_list{0}.DESCRIPTIO,_list{0}.DIAMETER,_list{0}.EPSG,_list{0}.Eindeutige ID,_list{0}.FEHLER,_list{0}.GEMEINDE,_list{0}.GEODINGUID_STGENER,_list{0}.GEODINGUID_STLAYER,_list{0}.GEODINGUID_STLYRTIT,_list{0}.GEOLDATBED,_list{0}.GRADUATION,_list{0}.GRAINSHAPE,_list{0}.GRAINSIZE1,_list{0}.GRAINSIZE2,_list{0}.GROBBESTAN,_list{0}.GROUNDWATE,_list{0}.GRUND,_list{0}.HRS,_list{0}.HUMIDITY,_list{0}.INKLINAT,_list{0}.INTART,_list{0}.INTART_1,_list{0}.INTKLASSE,_list{0}.INTV,_list{0}.InfoGeol,_list{0}.KANTON,_list{0}.KIROST,_list{0}.KLUEFTUNG,_list{0}.KORNRUNDU,_list{0}.LAGEOQID,_list{0}.LAND,_list{0}.LANDNUTZNG,_list{0}.LAYERDESC,_list{0}.LETZTBEARB,_list{0}.LETZTBEARB_1,_list{0}.LETZTBEARB_2,_list{0}.LITHOK,_list{0}.LITHOLOGY,_list{0}.LITHOSTRAT,_list{0}.LITPETGROB,_list{0}.LITTOPBED,_list{0}.LONGNAME,_list{0}.NAMEPUB,_list{0}.ORGANICOMP,_list{0}.ORIGGEOL,_list{0}.ORIGNAME,_list{0}.Original ID,_list{0}.PLASTICITY,_list{0}.PROCESSOR,_list{0}.PROJEKTNAM,_list{0}.QC Top Fels,_list{0}.QCBESCHR,_list{0}.QCBOHRUNG,_list{0}.QCCOORDEN,_list{0}.QCELEVATIZ,_list{0}.QCINKRICHT,_list{0}.QCTIEFE,_list{0}.QCTOPBED,_list{0}.RESTRICDAT,_list{0}.RESTRICTIO,_list{0}.RICHTUNG,_list{0}.SHORTNAME,_list{0}.SOILSTATE,_list{0}.STATUSBOHR,_list{0}.STRASSE,_list{0}.STRATOPDEB,_list{0}.STRIAE,_list{0}.TECTO,_list{0}.TIEFEMD,_list{0}.TOPBEDROCK,_list{0}.USCS1,_list{0}.USCS2,_list{0}.USCS3,_list{0}.USCSBEST,_list{0}.USCSORIGIN,_list{0}.XCOORD,_list{0}.YCOORD,_list{0}.ZCOORDB,_list{0}.ZCOORDE,_list{0}.debris,_list{0}.geomol,_list{0}.geoquat,_list{0}.geotherm,_list{0}.kantons ID,_list{0}.stratigraphy_id,_list{0}.stratigraphy_name,_list{0}.symbol,_list{0}.test,_list{0}.unconrocks,debris,geomol,geoquat,geotherm,kantons ID,stratigraphy_id,stratigraphy_name,symbol,test,unconrocks
    -> bh_raw (writer CSV2_3)
bh_raw (writer CSV2_3)
    attributes: LONGNAME varchar(255), ZCOORDE varchar(255), SHORTNAME varchar(255), PROJEKTNAM varchar(255), ORIGNAME varchar(255), BOHRTYP varchar(255), NAMEPUB varchar(255), QCCOORDEN varchar(255), QCELEVATIZ varchar(255), TIEFEMD varchar(255), QCTIEFE varchar(255), BOHREDAT varchar(255), LAND varchar(255), KANTON varchar(255), GEMEINDE varchar(255), STRASSE varchar(255), RESTRICTIO varchar(255), RESTRICDAT varchar(255), BMETHOD varchar(255), BOHRGUT varchar(255), BOHRZWECK varchar(255), STATUSBOHR varchar(255), TOPBEDROCK varchar(255), QCTOPBED varchar(255), GROUNDWATE varchar(255), DIAMETER varchar(255), INKLINAT varchar(255), RICHTUNG varchar(255), QCINKRICHT varchar(255), LITTOPBED varchar(255),
      STRATOPDEB varchar(255), CHROTOPBED varchar(255), EPSG varchar(255), HRS varchar(255), ARTANSATZZ varchar(255), LANDNUTZNG varchar(255), BEARBSTATU varchar(255), GEOLDATBED varchar(255), ATTRIBEARB varchar(255), ANZSCHICHT varchar(255), BEMERKUNG varchar(255), FEHLER varchar(255), LETZTBEARB varchar(255), BEARBDATUM varchar(255), GEODINGUID_STGENER varchar(255), INTV varchar(255), INTART varchar(255), GRUND varchar(255), QCBOHRUNG varchar(255), LETZTBEARB_1 varchar(255), BEARBDATUM_1 varchar(255), BAUGRDKLAS varchar(255), GEODINGUID_STLYRTIT varchar(255), DEPTHFROM varchar(255), DEPTHTO varchar(255), LAYERDESC varchar(255), DESCRIPTIO varchar(255), BESCHRSTAN varchar(255), QCBESCHR varchar(255), LITHOLOGY varchar(255),
      LITHOSTRAT varchar(255), CHRONOSTR varchar(255), TECTO varchar(255), COLOUR varchar(255), HUMIDITY varchar(255), PLASTICITY varchar(255), CONSISTENC varchar(255), COMPACTNES varchar(255), SOILSTATE varchar(255), ALTERATION varchar(255), GRADUATION varchar(255), ORGANICOMP varchar(255), STRIAE varchar(255), GRAINSIZE1 varchar(255), GRAINSHAPE varchar(255), GRAINSIZE2 varchar(255), COHESION varchar(255), USCS1 varchar(255), USCS2 varchar(255), USCS3 varchar(255), USCSBEST varchar(255), GROBBESTAN varchar(255), LITPETGROB varchar(255), CLASSDESOL varchar(255), PROCESSOR varchar(255), DATEPRO varchar(255), KORNRUNDU varchar(255), BOHRENDTIE varchar(255), LITHOK varchar(255), KIROST varchar(255),
      ADDPROPS varchar(255), KLUEFTUNG varchar(255), USCSORIGIN varchar(255), INTART_1 varchar(255), INTKLASSE varchar(255), COMMENTARY varchar(255), ORIGGEOL varchar(255), LAGEOQID varchar(255), LETZTBEARB_2 varchar(255), BEARBDATUM_2 varchar(255), GEODINGUID_STLAYER varchar(255), XCOORD varchar(255), YCOORD varchar(255), ZCOORDB varchar(255)
Sorter
    SORT_PARM = depth_from NATURAL DESCENDING id NATURAL ASCENDING
    SORTED -> DuplicateFilter
DuplicateFilter
    INPUT_ORDERED_CHOICE = No
    KEYATTR = id
    UNIQUE -> ChartGenerator
ChartGenerator
    AXES_FONT = Arial,12
    AXES_LW = 0.5
    BACKGROUND_COLOR = 1,1,1
    CHART_SETUP = SUMMARY_DATA;Tiefe (MD) [m];NUM_BINS;7;COLOR;0,0,1;TREND_LINE;NO;FME_CONTROLLER_QUERY_FILE;transformers/dependencies/charter/Histogram.fme;FME_CONTROLLER_CHOICE;Histogram
    CHART_TYPE = Histogram
    DPI = 300
    INTERPRETATION = RGBA32
    LEGEND_OPTIONS = NO
    TICKS = T
    TICK_FONT = Arial,10
    TITLE_FONT = Arial,12
    X_INCH = 2.0
    X_LABEL = Depth (MD)
    X_LABEL_ANGLE = Horizontal (0)
    X_LOG = LIN
    Y_INCH = 2.0
    Y_LABEL = Nb
    Y_LABEL_ANGLE = Horizontal (0)
    Y_LOG = LOG
test_rheinau (reader XLSXR_1)
    attributes: id number(3,0), Originalname char(27), Projektname char(115), Name öffentlich char(27), Bohrtyp date, Restriktion date, Restriktion Datum string, Koordinate E number(12,3), Koordinate N number(12,3), SRS number(9,0), QC Koordinaten number(9,0), HRS number(9,0), QC Ansatz Z number(9,0), Landnutzung string, Kanton char(13), Gemeinde char(10), Strasse string, Bohrmethode number(9,0), Bohrende Datum date, Bohrgut number(9,0), Bohrzweck number(9,0), Bohrduchmesser string, Status Bohrloch number(9,0), TAN Inklination number(31,18), TAN Einfallsrichtung number(19,15), QC Inc/Richtung number(8,0), Tiefe (MD) [m] number(6,1), Endteufe (TVD) number(9,5), X Offset number(31,15), Y Offset number(31,15),
      XCOORD number(12,3), YCOORD number(12,3), QC Tiefe number(9,0), Top Fels [m] number(3,0), QC Top Fels number(9,0), Grundwasser string, stratigraphy_id number(3,0), stratigraphy_name char(19), depth_from number(6,1), depth_to number(9,5), description char(202), geology string, qt_description number(5,0), lithology number(9,0), lithostratigraphy number(9,0), chronostratigraphy date, tectonic_unit string, symbol string, color string, plasticity date, humidity date, consistance number(9,0), alteration string, compactness string, jointing string, soil_state number(9,0), organic_component string, striae string, grain_size_1 string, grain_size_2 string,
      grain_shape string, grain_granularity string, further_properties string, uscs_1 string, uscs_2 string, uscs_3 string, uscs_original string, uscs_determination string, unconrocks string, debris string, lit_pet_deb string, lithok string, kirost string, notes char(256), Eindeutige ID string, CH string, InfoGeol string, Original ID string, geoquat string, geomol string, geotherm string, kantons ID string, test string, delta X Offset x_coordinate, delta Y Offset y_coordinate, Ansatzhöhe Z [müM] z_coordinate
    -> Tester [off]
Tester
    BOOL_OP = OR
    COMPOSITE_TEST = 1
    TEST_CLAUSE = TEST @Value(id) = 34
    TEST_MODE = TEST
    PASSED -> AttributeKeeper_6 [off]
AttributeKeeper_6
    CREATE_BULK_MODE_FEATURES = NO
    KEEP_ATTRS = Bohrduchmesser,depth_from,depth_to,id,Restriktion,Top Fels [m],Koordinate E,Koordinate N,lithology,Name öffentlich,Projektname,Ansatzhöhe Z [müM],Tiefe (MD) [m]
    -> AttributeCreator_6
    -> AttributeCreator_3
Note: überprüfen: mapping von SF script hier bereits vollständig enthalten?
AttributeKeeper_5
    CREATE_BULK_MODE_FEATURES = NO
    KEEP_ATTRS = DEPTHFROM,DEPTHTO,DIAMETER,LITHOLOGY,RESTRICTIO,SHORTNAME,TOPBEDROCK,XCOORD,YCOORD,ZCOORDB,INKLINAT,NAMEPUB,TIEFEMD,BOHREDAT,BOHRTYP,CHRONOSTR,GRUND,LAYERDESC,LITHOSTRAT,ORIGGEOL,ORIGNAME,TECTO,USCS1,USCS2,USCS3
    -> AttributeRenamer_2
AttributeRenamer_2
    ATTR_TABLE:
      RENAME_SET_DEFAULT SHORTNAME > id
      RENAME_SET_DEFAULT NAMEPUB > Name öffentlich
      RENAME_SET_DEFAULT RESTRICTIO > Restriktion
      RENAME_SET_DEFAULT TOPBEDROCK > Top Fels [m]
      RENAME_SET_DEFAULT DIAMETER > Bohrduchmesser
      RENAME_SET_DEFAULT INKLINAT > Inklination
      RENAME_SET_DEFAULT DEPTHFROM > depth_from
      RENAME_SET_DEFAULT DEPTHTO > depth_to
      RENAME_SET_DEFAULT LITHOLOGY > lithology
      RENAME_SET_DEFAULT XCOORD > Koordinate E
      RENAME_SET_DEFAULT YCOORD > Koordinate N
      RENAME_SET_DEFAULT ZCOORDB > Ansatzhöhe Z [müM]
      RENAME_SET_DEFAULT TIEFEMD > Tiefe (MD) [m]
    MISSING_INPUT_ATTRS = REMOVE
    -> AttributeCreator_6 [off]
    -> AttributeCreator_3 [off]
Sorter_5
    GROUP_BY = "BH_ID select"
    SORT_PARM = depth_from NUMERIC DESCENDING
    SORTED -> FeatureMerger_5 [REQUESTOR]
File1 (writer OBJ_1)
BH2_cesiumTiles_v2 (writer CESIUM3DTILES_1)
    attributes: Solid_Unconsolidated string, BH_ID select string, Layer ID select string, id int, Projektname string, Name öffentlich string, Restriktion string, Koordinate E float, Koordinate N float, Bohrduchmesser string, Tiefe (MD) [m] float, Top Fels [m] int, depth_from float, depth_to float, lithology int, Ansatzhöhe Z [müM] float, Inklination string, BH_Geometry_X float, BH_Geometry_Y float, BH_Geometry_Z string, xgeom float, ygeom float, zgeom string, _countElement int, fme_rejection_code string
AttributeKeeper
    CREATE_BULK_MODE_FEATURES = NO
    KEEP_ATTRS = Bohrduchmesser,BOHREDAT,BOHRTYP,CHRONOSTR,DEPTHFROM,DEPTHTO,GRUND,Inklination,LAYERDESC,LITHOLOGY,LITHOSTRAT,NAMEPUB,ORIGNAME,RESTRICTIO,SHORTNAME,TECTO,TIEFEMD,Top Fels [m],USCS1,USCS3,USCS100

Bookmark: input interval table
AttributeCreator_3
    ATTR_TABLE:
      SET_TO BH_ID select = $(BH_ID)
      SET_TO Layer ID select = $(LayerID_select)
    -> Sorter_5

Bookmark: Input geometry xyz table
AttributeCreator_6
    ATTR_TABLE:
      SET_TO xgeom = @Value(Koordinate E)
      SET_TO ygeom = @Value(Koordinate N)
      SET_TO zgeom = @Evaluate(@Value(Ansatzhöhe Z [müM])-@Value(depth_from))
    -> AttributeKeeper_7
AttributeKeeper_7
    CREATE_BULK_MODE_FEATURES = NO
    KEEP_ATTRS = id,xgeom,ygeom,zgeom,Restriktion,Top Fels [m],Ansatzhöhe Z [müM],depth_from,depth_to
    -> AttributeCreator_5

Bookmark: Input geometry
AttributeCreator_5
    ATTR_TABLE:
      SET_TO BH_ID select = $(BH_ID)
      SET_TO BH_Geometry_X = @Value(xgeom)
      SET_TO BH_Geometry_Y = @Value(ygeom)
      SET_TO BH_Geometry_Z = @Value(zgeom)
    -> Sorter_4

Bookmark: Build line for every borehole id
Note: Sorted from base to top
Sorter_4
    SORT_PARM = BH_Geometry_Z NUMERIC DESCENDING
    SORTED -> VertexCreator_3
Note: A vertex is built at every coordinate
VertexCreator_3
    MEASURE_TYPE = Continuous
    MODE_NAME = Replace with Point
    XVAL = @Value(BH_Geometry_X)
    YVAL = @Value(BH_Geometry_Y)
    ZVAL = @Value(BH_Geometry_Z)
    -> CoordinateSwapper_3 [off]
    -> VertexCreator_4
Note: Only usefull for swissforage export (layers), not for drillpath (paths)
VertexCreator_4
    IGNORE_DUPLICATES = No
    MEASURE_TYPE = Continuous
    MISSING_VAL_MODE = Compute
    MODE_NAME = Add Point
    XVAL = @Value(BH_Geometry_X)
    YVAL = @Value(BH_Geometry_Y)
    ZVAL = @Evaluate(@Value(Ansatzhöhe Z [müM])-@Value(depth_to))
    -> CoordinateSwapper_3
CoordinateSwapper_3
    SWAP_TYPE = X <-> Z
    -> LineBuilder_2
LineBuilder_2
    ACCUM_INPUT_ATTRS = Use Attributes From One Feature
    GROUP_BY = "BH_ID select"
    REMOVE_DUPLICATES = No
    LINE -> CoordinateSwapper_4
CoordinateSwapper_4
    SWAP_TYPE = X <-> Z
    -> FeatureMerger_5 [SUPPLIER]

Bookmark: Build pipe segments
FeatureMerger_5
    ATTR_ACCUM_MODE = Merge Supplier
    ATTR_CONFLICT_RES = Use Requestor
    IGNORE_NULLS = No
    JOIN_KEYS = @Value(BH_ID select) @Value(BH_ID select) AUTO
    MERGE_TYPE = Attributes and Geometry
    PROCESS_DUPS = NO
    REJECT_NULL_MISSING_KEYS = No
    SUPPLIERS_FIRST = No
    MERGED -> Snipper_2
Note: Boreholes are cut into layer segments
Snipper_2
    DEAGGREGATE_INPUT = YES
    ENDLOCATIONATTR = @Value(depth_to)
    MEASUREMENTTYPE = 3D
    SNIPMODE = Distance (Value)
    STARTLOCATIONATTR = @Value(depth_from)
    -> PipeReplacer_3
PipeReplacer_3
    OUTER_RADIUS = $(BH_Diameter)
    -> Dissolver
Dissolver
    ACCUM_INPUT_ATTRS = Use Attributes From One Feature
    CLEANING_TOLERANCE = Automatic
    CONNECT_Z_MODE = First Wins
    DEAGGREGATE_INPUT = Yes
    GROUP_BY = lithology
    AREA -> AttributeCreator

Bookmark: Select color attribute
AttributeCreator
    ATTR_TABLE = SET_TO Solid_Unconsolidated = FME_CONDITIONAL:DEFAULT_VALUE'Unconsolidated'BOOL_OP;OR;COMPOSITE_TEST;1;TEST @Value(depth_from) >= @Value(Top Fels [m])'Solid'FME_NUM_CONDITIONS2___
    -> FeatureColorSetter
FeatureColorSetter
    MODE = Random
    RANDOM_COLOR_CAP = 0
    RANDOM_MODE = Attributes
    COLORED -> Counter_3
Counter_3
    CNT_ATTR = _countElement
    DOMAIN = counter
    SCOPE = Local
    START = 1
    -> CoordinateSystemSetter_2
CoordinateSystemSetter_2
    COORDSYS = CH1903Plus_1.LV95/01
    -> AppearanceRemover_2
    -> GeometryRemover_2
GeometryRemover_2
    -> AttributeKeeper_2
AttributeKeeper_2
    CREATE_BULK_MODE_FEATURES = NO
    KEEP_ATTRS = fme_color,_countElement
    -> AppearanceStyler_2
AppearanceStyler_2
    ALPHA = 1.0
    DIFFUSE_COLOR = @Value(fme_color)
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_2 [APPEARANCE]
AppearanceRemover_2
    SIDE_TO_REMOVE = Front and Back Sides
    -> GeometryPropertySetter_2
    <REJECTED> -> GeometryPropertySetter_2
GeometryPropertySetter_2
    OVERWRITE_CHOICE = Yes
    REMOVE_ATTRIBUTE = No
    SETTYPE_PARAM = Traits From Attributes
    SRC_ATTRS = fme_color
    SET -> AppearanceSetter_2 [GEOMETRY]
AppearanceSetter_2
    DEF_STORAGE = Create New Definitions
    GQUERY:
      for $geom in //geometry
      where $geom/count(parent::geometry) = 0
      return number($geom/@fme_id)
    JOIN_ATTR = fme_color
    JOIN_TRAIT = fme_color
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> BH2_cesiumTiles_v2 (writer CESIUM3DTILES_1)
    -> File1 (writer OBJ_1)
