FME workspace BH_2_CesiumTiles_070622_pipereplacer.fmw

Parameters:
- BH_Diameter =
- BH_ID =
- DestDataset_CESIUM3DTILES =
- DestDataset_OBJ =
- LayerID_select =
- SourceDataset_CSV2 =
- SourceDataset_CSV2_3 =
- SourceDataset_XLSXR =

Readers:
- XLSXR_1: XLSXR from $(SourceDataset_XLSXR)
- CSV2_1: CSV2 from $(SourceDataset_CSV2)
- CSV2_2: CSV2 from $(SourceDataset_CSV2_3)

Writers:
- CESIUM3DTILES_1: CESIUM3DTILES to $(DestDataset_CESIUM3DTILES) in EPSG:4326
- OBJ_1: OBJ to $(DestDataset_OBJ)

Note: Export Swissforage
CSV (reader CSV2_1)
    attributes: id uint32, Originalname varchar(74), Projektname varchar(251), Name öffentlich varchar(74), Bohrtyp date, Restriktion date, Restriktion Datum varchar(11), Koordinate E real64, Koordinate N real64, SRS date, QC Koordinaten date, Ansatzhöhe Z [müM] real32, HRS date, QC Ansatz Z date, Landnutzung date, Kanton varchar(13), Gemeinde varchar(24), Strasse varchar(30), Bohrmethode date, Bohrende Datum varchar(11), Bohrgut date, Bohrzweck date, Bohrduchmesser real32, Status Bohrloch date, Inklination real32, Einfallsrichtung real32, QC Inc/Richtung uint32, Tiefe (MD) [m] real32, QC Tiefe date, Top Fels [m] real32,
      QC Top Fels date, Grundwasser varchar(6), stratigraphy_id uint32, stratigraphy_name varchar(44), depth_from real32, depth_to real32, description varchar(12806), geology varchar(254), qt_description uint32, lithology real64, lithostratigraphy real64, chronostratigraphy date, tectonic_unit varchar(1), symbol varchar(1), color varchar(63), plasticity date, humidity date, consistance date, alteration date, compactness date, jointing varchar(1), soil_state date, organic_component real64, striae varchar(6), grain_size_1 date, grain_size_2 date, grain_shape varchar(1), grain_granularity varchar(27), further_properties date, uscs_1 date,
      uscs_2 date, uscs_3 varchar(1), uscs_original varchar(1), uscs_determination date, unconrocks varchar(1), debris uint32, lit_pet_deb varchar(1), lithok varchar(1), kirost varchar(1), notes varchar(9782), Eindeutige ID varchar(1), CH varchar(1), InfoGeol varchar(1), Original ID varchar(1), geoquat varchar(1), geomol varchar(1), geotherm varchar(1), kantons ID varchar(1), test varchar(1)
    -> AttributeKeeper_6
AttributeKeeper_6
    CREATE_BULK_MODE_FEATURES = NO
    KEEP_ATTRS = Bohrduchmesser,depth_from,depth_to,id,Inklination,Restriktion,Top Fels [m],Koordinate E,Koordinate N,lithology,Name öffentlich,Projektname,Ansatzhöhe Z [müM],Tiefe (MD) [m]
    -> AttributeCreator_6
    -> AttributeCreator_3
Note: GeoDIN Daten
Export (reader XLSXR_1)
    attributes: LONGNAME char(27), ZCOORDE number(2,0), SHORTNAME char(11), PROJEKTNAM char(70), ORIGNAME char(14), BOHRTYP char(3), NAMEPUB char(14), QCCOORDEN number(2,0), QCELEVATIZ number(2,0), TIEFEMD number(7,2), QCTIEFE number(2,0), BOHREDAT char(11), LAND char(3), KANTON char(3), GEMEINDE number(5,0), STRASSE string, RESTRICTIO char(2), RESTRICDAT string, BMETHOD char(5), BOHRGUT char(3), BOHRZWECK char(9), STATUSBOHR char(3), TOPBEDROCK number(8,2), QCTOPBED number(2,0), GROUNDWATE char(2), DIAMETER string, INKLINAT number(3,0), RICHTUNG number(2,0), QCINKRICHT char(6), LITTOPBED char(6),
      STRATOPDEB string, CHROTOPBED char(4), EPSG number(5,0), HRS char(5), ARTANSATZZ char(4), LANDNUTZNG string, BEARBSTATU char(5), GEOLDATBED char(4), ATTRIBEARB char(4), ANZSCHICHT number(2,0), BEMERKUNG string, FEHLER string, LETZTBEARB char(10), BEARBDATUM datetime, GEODINGUID_STGENER char(39), INTV number(2,0), INTART char(3), GRUND char(8), QCBOHRUNG number(4,1), LETZTBEARB_1 char(10), BEARBDATUM_1 date, BAUGRDKLAS string, GEODINGUID_STLYRTIT char(39), DEPTHFROM number(6,2), DEPTHTO number(6,2), LAYERDESC char(290), DESCRIPTIO string, BESCHRSTAN string, QCBESCHR number(2,0), LITHOLOGY char(6),
      LITHOSTRAT string, CHRONOSTR char(4), TECTO string, COLOUR string, HUMIDITY char(5), PLASTICITY char(3), CONSISTENC char(4), COMPACTNES char(3), SOILSTATE string, ALTERATION char(5), GRADUATION string, ORGANICOMP char(9), STRIAE char(2), GRAINSIZE1 char(6), GRAINSHAPE char(4), GRAINSIZE2 char(6), COHESION char(3), USCS1 char(6), USCS2 char(6), USCS3 char(9), USCSBEST char(5), GROBBESTAN char(5), LITPETGROB char(6), CLASSDESOL string, PROCESSOR string, DATEPRO string, KORNRUNDU char(10), BOHRENDTIE char(2), LITHOK char(3), KIROST char(3),
      ADDPROPS char(3), KLUEFTUNG string, USCSORIGIN char(9), INTART_1 string, INTKLASSE string, COMMENTARY char(3), ORIGGEOL char(42), LAGEOQID string, LETZTBEARB_2 char(10), BEARBDATUM_2 date, GEODINGUID_STLAYER char(39), XCOORD x_coordinate, YCOORD y_coordinate, ZCOORDB z_coordinate
    -> AttributeKeeper_5
AttributeKeeper_5
    CREATE_BULK_MODE_FEATURES = NO
    KEEP_ATTRS = DEPTHFROM,DEPTHTO,DIAMETER,LITHOLOGY,RESTRICTIO,SHORTNAME,TOPBEDROCK,XCOORD,YCOORD,ZCOORDB,INKLINAT,NAMEPUB,PROJEKTNAM,TIEFEMD
    -> AttributeRenamer_2
AttributeRenamer_2
    ATTR_TABLE:
      RENAME_SET_DEFAULT SHORTNAME > id
      RENAME_SET_DEFAULT PROJEKTNAM > Projektname
      RENAME_SET_DEFAULT NAMEPUB > Name öffentlich
      RENAME_SET_DEFAULT RESTRICTIO > Restriktion
      RENAME_SET_DEFAULT TOPBEDROCK > Top Fels [m]
      RENAME_SET_DEFAULT DIAMETER > Bohrduchmesser
      RENAME_SET_DEFAULT INKLINAT > Inklination
      RENAME_SET_DEFAULT DEPTHFROM > depth_from
      RENAME_SET_DEFAULT DEPTHTO > depth_to
      RENAME_SET_DEFAULT LITHOLOGY > lithology
      RENAME_SET_DEFAULT XCOORD > Koordinate E
      RENAME_SET_DEFAULT YCOORD > Koordinate N
      RENAME_SET_DEFAULT ZCOORDB > Ansatzhöhe Z [müM]
      RENAME_SET_DEFAULT TIEFEMD > Tiefe (MD) [m]
    MISSING_INPUT_ATTRS = REMOVE
    -> AttributeCreator_6
    -> AttributeCreator_3
Note: how to display data?
BH2_cesiumTiles_v2 (writer CESIUM3DTILES_1)
    attributes: BH_ID select string, Layer ID select string, id int, Projektname string, Name öffentlich string, Restriktion string, Koordinate E float, Koordinate N float, Ansatzhöhe Z [müM] float, Bohrduchmesser float, Inklination float, Tiefe (MD) [m] float, Top Fels [m] float, depth_from float, depth_to float, lithology float, BH_Geometry_X float, BH_Geometry_Y float, BH_Geometry_Z string, xgeom float, ygeom float, zgeom string, _countElement int
File1 (writer OBJ_1)

Bookmark: input interval table
AttributeCreator_3
    ATTR_TABLE:
      SET_TO BH_ID select = $(BH_ID)
      SET_TO Layer ID select = $(LayerID_select)
    -> Sorter_5

Bookmark: TEMPORARY Attention: last segment will be removed
Sorter_5
    GROUP_BY = "BH_ID select"
    SORT_PARM = depth_from NUMERIC DESCENDING
    SORTED -> Sampler
Sampler
    GROUP_BY = "BH_ID select"
    RATE = 1
    SAMPLE_MODE = No
    SAMPLE_TYPE_LONG = First N Features
    NOT_SAMPLED -> FeatureMerger_5 [REQUESTOR]

Bookmark: Input geometry xyz table
AttributeCreator_6
    ATTR_TABLE:
      SET_TO xgeom = @Value(Koordinate E)
      SET_TO ygeom = @Value(Koordinate N)
      SET_TO zgeom = @Evaluate(@Value(Ansatzhöhe Z [müM])-@Value(depth_from))
    -> AttributeKeeper_7
AttributeKeeper_7
    CREATE_BULK_MODE_FEATURES = NO
    KEEP_ATTRS = id,xgeom,ygeom,zgeom
    -> AttributeCreator_5

Bookmark: Input geometry
AttributeCreator_5
    ATTR_TABLE:
      SET_TO BH_ID select = $(BH_ID)
      SET_TO BH_Geometry_X = @Value(xgeom)
      SET_TO BH_Geometry_Y = @Value(ygeom)
      SET_TO BH_Geometry_Z = @Value(zgeom)
    -> Sorter_4

Bookmark: Build line from geometry
Sorter_4
    SORT_PARM = BH_Geometry_Z NUMERIC DESCENDING
    SORTED -> VertexCreator_3
VertexCreator_3
    MEASURE_TYPE = Continuous
    MODE_NAME = Replace with Point
    XVAL = @Value(BH_Geometry_X)
    YVAL = @Value(BH_Geometry_Y)
    ZVAL = @Value(BH_Geometry_Z)
    -> FeatureColorSetter
    -> CoordinateSwapper_3
CoordinateSwapper_3
    SWAP_TYPE = X <-> Z
    -> LineBuilder_2
LineBuilder_2
    ACCUM_INPUT_ATTRS = Use Attributes From One Feature
    GROUP_BY = "BH_ID select"
    REMOVE_DUPLICATES = No
    LINE -> CoordinateSwapper_4
CoordinateSwapper_4
    SWAP_TYPE = X <-> Z
    -> FeatureMerger_5 [SUPPLIER]

Bookmark: Build pipe segments
FeatureMerger_5
    ATTR_ACCUM_MODE = Merge Supplier
    ATTR_CONFLICT_RES = Use Requestor
    IGNORE_NULLS = No
    JOIN_KEYS = @Value(BH_ID select) @Value(BH_ID select) AUTO
    MERGE_TYPE = Attributes and Geometry
    PROCESS_DUPS = NO
    REJECT_NULL_MISSING_KEYS = No
    SUPPLIERS_FIRST = No
    MERGED -> Snipper_2
Snipper_2
    DEAGGREGATE_INPUT = YES
    ENDLOCATIONATTR = @Value(depth_to)
    MEASUREMENTTYPE = 3D
    SNIPMODE = Distance (Value)
    STARTLOCATIONATTR = @Value(depth_from)
    -> PipeReplacer_3
PipeReplacer_3
    OUTER_RADIUS = $(BH_Diameter)
    -> FeatureColorSetter

Bookmark: Select color attrb
FeatureColorSetter
    MODE = Random
    RANDOM_COLOR_CAP = 0
    RANDOM_MODE = Attributes
    COLORED -> Counter_3
Counter_3
    CNT_ATTR = _countElement
    DOMAIN = counter
    SCOPE = Local
    START = 1
    -> CoordinateSystemSetter_2
CoordinateSystemSetter_2
    COORDSYS = CH1903Plus_1.LV95/01
    -> AppearanceRemover_2
    -> GeometryRemover_2
GeometryRemover_2
    -> AttributeKeeper_2
AttributeKeeper_2
    CREATE_BULK_MODE_FEATURES = NO
    KEEP_ATTRS = fme_color,_countElement
    -> AppearanceStyler_2
AppearanceStyler_2
    ALPHA = 1.0
    DIFFUSE_COLOR = @Value(fme_color)
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_2 [APPEARANCE]
AppearanceRemover_2
    SIDE_TO_REMOVE = Front and Back Sides
    -> GeometryPropertySetter_2
Note: ?
GeometryPropertySetter_2
    OVERWRITE_CHOICE = Yes
    REMOVE_ATTRIBUTE = No
    SETTYPE_PARAM = Traits From Attributes
    SRC_ATTRS = fme_color
    SET -> AppearanceSetter_2 [GEOMETRY]
AppearanceSetter_2
    DEF_STORAGE = Create New Definitions
    GQUERY:
      for $geom in //geometry
      where $geom/count(parent::geometry) = 0
      return number($geom/@fme_id)
    JOIN_ATTR = fme_color
    JOIN_TRAIT = fme_color
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> BH2_cesiumTiles_v2 (writer CESIUM3DTILES_1)
