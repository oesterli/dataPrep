FME workspace BH_2_CesiumTiles_070622.fmw

Parameters:
- BH_Diameter =
- BH_ID =
- DestDataset_CESIUM3DTILES =
- LayerID_select =
- SourceDataset_CSV2 =
- SourceDataset_CSV2_3 =
- SourceDataset_XLSXR =

Readers:
- XLSXR_1: XLSXR from $(SourceDataset_XLSXR)
- CSV2_1: CSV2 from $(SourceDataset_CSV2)
- CSV2_2: CSV2 from $(SourceDataset_CSV2_3)

Writers:
- CESIUM3DTILES_1: CESIUM3DTILES to $(DestDataset_CESIUM3DTILES) in EPSG:4326

Note: Export Swissforage
CSV (reader CSV2_1)
    attributes: id uint32, Originalname varchar(74), Projektname varchar(251), Name öffentlich varchar(74), Bohrtyp date, Restriktion date, Restriktion Datum varchar(11), Koordinate E real64, Koordinate N real64, SRS date, QC Koordinaten date, Ansatzhöhe Z [müM] real32, HRS date, QC Ansatz Z date, Landnutzung date, Kanton varchar(13), Gemeinde varchar(24), Strasse varchar(30), Bohrmethode date, Bohrende Datum varchar(11), Bohrgut date, Bohrzweck date, Bohrduchmesser real32, Status Bohrloch date, Inklination real32, Einfallsrichtung real32, QC Inc/Richtung uint32, Tiefe (MD) [m] real32, QC Tiefe date, Top Fels [m] real32,
      QC Top Fels date, Grundwasser varchar(6), stratigraphy_id uint32, stratigraphy_name varchar(44), depth_from real32, depth_to real32, description varchar(12806), geology varchar(254), qt_description uint32, lithology real64, lithostratigraphy real64, chronostratigraphy date, tectonic_unit varchar(1), symbol varchar(1), color varchar(63), plasticity date, humidity date, consistance date, alteration date, compactness date, jointing varchar(1), soil_state date, organic_component real64, striae varchar(6), grain_size_1 date, grain_size_2 date, grain_shape varchar(1), grain_granularity varchar(27), further_properties date, uscs_1 date,
      uscs_2 date, uscs_3 varchar(1), uscs_original varchar(1), uscs_determination date, unconrocks varchar(1), debris uint32, lit_pet_deb varchar(1), lithok varchar(1), kirost varchar(1), notes varchar(9782), Eindeutige ID varchar(1), CH varchar(1), InfoGeol varchar(1), Original ID varchar(1), geoquat varchar(1), geomol varchar(1), geotherm varchar(1), kantons ID varchar(1), test varchar(1)
    -> AttributeKeeper_6
AttributeKeeper_6
    CREATE_BULK_MODE_FEATURES = NO
    KEEP_ATTRS = Bohrduchmesser,depth_from,depth_to,id,Inklination,Restriktion,Top Fels [m],Koordinate E,Koordinate N,lithology,Name öffentlich,Projektname,Ansatzhöhe Z [müM],Tiefe (MD) [m]
    -> AttributeCreator_5
Note: GeoDIN Daten
Export (reader XLSXR_1)
    attributes: LONGNAME char(27), ZCOORDE number(2,0), SHORTNAME char(11), PROJEKTNAM char(70), ORIGNAME char(14), BOHRTYP char(3), NAMEPUB char(14), QCCOORDEN number(2,0), QCELEVATIZ number(2,0), TIEFEMD number(7,2), QCTIEFE number(2,0), BOHREDAT char(11), LAND char(3), KANTON char(3), GEMEINDE number(5,0), STRASSE string, RESTRICTIO char(2), RESTRICDAT string, BMETHOD char(5), BOHRGUT char(3), BOHRZWECK char(9), STATUSBOHR char(3), TOPBEDROCK number(8,2), QCTOPBED number(2,0), GROUNDWATE char(2), DIAMETER string, INKLINAT number(3,0), RICHTUNG number(2,0), QCINKRICHT char(6), LITTOPBED char(6),
      STRATOPDEB string, CHROTOPBED char(4), EPSG number(5,0), HRS char(5), ARTANSATZZ char(4), LANDNUTZNG string, BEARBSTATU char(5), GEOLDATBED char(4), ATTRIBEARB char(4), ANZSCHICHT number(2,0), BEMERKUNG string, FEHLER string, LETZTBEARB char(10), BEARBDATUM datetime, GEODINGUID_STGENER char(39), INTV number(2,0), INTART char(3), GRUND char(8), QCBOHRUNG number(4,1), LETZTBEARB_1 char(10), BEARBDATUM_1 date, BAUGRDKLAS string, GEODINGUID_STLYRTIT char(39), DEPTHFROM number(6,2), DEPTHTO number(6,2), LAYERDESC char(290), DESCRIPTIO string, BESCHRSTAN string, QCBESCHR number(2,0), LITHOLOGY char(6),
      LITHOSTRAT string, CHRONOSTR char(4), TECTO string, COLOUR string, HUMIDITY char(5), PLASTICITY char(3), CONSISTENC char(4), COMPACTNES char(3), SOILSTATE string, ALTERATION char(5), GRADUATION string, ORGANICOMP char(9), STRIAE char(2), GRAINSIZE1 char(6), GRAINSHAPE char(4), GRAINSIZE2 char(6), COHESION char(3), USCS1 char(6), USCS2 char(6), USCS3 char(9), USCSBEST char(5), GROBBESTAN char(5), LITPETGROB char(6), CLASSDESOL string, PROCESSOR string, DATEPRO string, KORNRUNDU char(10), BOHRENDTIE char(2), LITHOK char(3), KIROST char(3),
      ADDPROPS char(3), KLUEFTUNG string, USCSORIGIN char(9), INTART_1 string, INTKLASSE string, COMMENTARY char(3), ORIGGEOL char(42), LAGEOQID string, LETZTBEARB_2 char(10), BEARBDATUM_2 date, GEODINGUID_STLAYER char(39), XCOORD x_coordinate, YCOORD y_coordinate, ZCOORDB z_coordinate
    -> AttributeKeeper_5
AttributeKeeper_5
    CREATE_BULK_MODE_FEATURES = NO
    KEEP_ATTRS = DEPTHFROM,DEPTHTO,DIAMETER,LITHOLOGY,RESTRICTIO,SHORTNAME,TOPBEDROCK,XCOORD,YCOORD,ZCOORDB,INKLINAT,NAMEPUB,PROJEKTNAM,TIEFEMD
    -> AttributeRenamer_2
AttributeRenamer_2
    ATTR_TABLE:
      RENAME_SET_DEFAULT SHORTNAME > id
      RENAME_SET_DEFAULT PROJEKTNAM > Projektname
      RENAME_SET_DEFAULT NAMEPUB > Name öffentlich
      RENAME_SET_DEFAULT RESTRICTIO > Restriktion
      RENAME_SET_DEFAULT TOPBEDROCK > Top Fels [m]
      RENAME_SET_DEFAULT DIAMETER > Bohrduchmesser
      RENAME_SET_DEFAULT INKLINAT > Inklination
      RENAME_SET_DEFAULT DEPTHFROM > depth_from
      RENAME_SET_DEFAULT DEPTHTO > depth_to
      RENAME_SET_DEFAULT LITHOLOGY > lithology
      RENAME_SET_DEFAULT XCOORD > Koordinate E
      RENAME_SET_DEFAULT YCOORD > Koordinate N
      RENAME_SET_DEFAULT ZCOORDB > Ansatzhöhe Z [müM]
      RENAME_SET_DEFAULT TIEFEMD > Tiefe (MD) [m]
    MISSING_INPUT_ATTRS = REMOVE
    -> AttributeCreator_5
AttributeCreator_5
    ATTR_TABLE:
      SET_TO BH_ID select = $(BH_ID)
      SET_TO Layer ID select = $(LayerID_select)
      SET_TO Coordinate X select
      SET_TO Coordinate Y select
      SET_TO Coordinate Z select
    -> VertexCreator_2
    -> VertexCreator
    -> AttributeValueMapper
Note: coordinates of top
VertexCreator
    MEASURE_TYPE = Continuous
    MODE_NAME = Replace with Point
    XVAL = @Value(Koordinate E)
    YVAL = @Value(Koordinate N)
    ZVAL = @Value(Ansatzhöhe Z [müM])-@Value(depth_from)
    -> CoordinateRounder_2
Note: coordinates of bottom
VertexCreator_2
    MEASURE_TYPE = Continuous
    MODE_NAME = Replace with Point
    XVAL = @Value(Koordinate E)
    YVAL = @Value(Koordinate N)
    ZVAL = @Value(Ansatzhöhe Z [müM])-@Value(depth_to)
    -> CoordinateRounder_2
CoordinateRounder_2
    XPREC = 2
    YPREC = 2
    ZPREC = 2
    ROUNDED -> LineBuilder
LineBuilder
    ACCUM_INPUT_ATTRS = Use Attributes From One Feature
    GROUP_BY = depth_from depth_to id
    REMOVE_DUPLICATES = Yes
    LINE -> AttributeCreator_4
AttributeCreator_4
    ATTR_TABLE = SET_TO BH_Radius = $(BH_Diameter)/2
    -> Sorter_3
Sorter_3
    SORT_PARM = "BH_ID select" ALPHA ASCENDING "Layer ID select" NUMERIC ASCENDING
    SORTED -> DuplicateFilter
    SORTED -> Counter_2
Tester_2
    BOOL_OP = OR
    COMPOSITE_TEST = 1
    TEST_CLAUSE = TEST @Value(_countBH) = 238
    TEST_MODE = TEST
    PASSED -> AttributeKeeper_8
AttributeKeeper_8
    CREATE_BULK_MODE_FEATURES = NO
    KEEP_ATTRS = _countBH,_countElements,BH_Radius
    -> VertexCounter
AttributeValueMapper
    DIRECTION = Forward (Source To Destination)
    VAL_ATTR = _looked_up
    -> ChartGenerator
ChartGenerator
    AXES_FONT = Arial,12
    AXES_LW = 0.5
    BACKGROUND_COLOR = 1,1,1
    CHART_SETUP = SUMMARY_DATA;Tiefe (MD) [m];NUM_BINS;7;COLOR;0,0,1;TREND_LINE;NO;FME_CONTROLLER_QUERY_FILE;transformers/dependencies/charter/Histogram.fme;FME_CONTROLLER_CHOICE;Histogram
    CHART_TITLE = Histogramm of Measured Depth
    CHART_TYPE = Histogram
    DPI = 300
    INTERPRETATION = RGBA32
    LEGEND_OPTIONS = NO
    TICKS = T
    TICK_FONT = Arial,10
    TITLE_FONT = Arial,12
    X_INCH = 2.0
    X_LABEL = Depth in km
    X_LABEL_ANGLE = Horizontal (0)
    X_LOG = LIN
    Y_INCH = 2.0
    Y_LABEL = Anzahl Bohrungen
    Y_LABEL_ANGLE = Horizontal (0)
    Y_LOG = LIN
Note: ?
Tester_8
    BOOL_OP = OR
    COMPOSITE_TEST = 1
    TEST_CLAUSE = TEST @Value(_countBH) = 5
    TEST_MODE = TEST
FeatureMerger_3
    ATTR_ACCUM_MODE = Merge Supplier
    ATTR_CONFLICT_RES = Use Requestor
    IGNORE_NULLS = No
    JOIN_KEYS = @Value(_countElements) @Value(_countElements) AUTO
    MERGE_TYPE = Attributes Only
    PROCESS_DUPS = NO
    REJECT_NULL_MISSING_KEYS = No
    SUPPLIERS_FIRST = No
    MERGED -> FeatureColorSetter
FeatureColorSetter
    MODE = Random
    RANDOM_COLOR_CAP = 0
    RANDOM_MODE = Attributes
    COLORED -> Counter_3
Counter_3
    CNT_ATTR = _countElement
    DOMAIN = counter
    SCOPE = Local
    START = 1
    -> CoordinateSystemSetter_2
CoordinateSystemSetter_2
    COORDSYS = CH1903Plus_1.LV95/01
    -> AppearanceRemover_2
    -> GeometryRemover_2
Note: how to display data?
BH2_cesiumTiles_v2 (writer CESIUM3DTILES_1)
    attributes: BH_Type string, BH_Radius string, _countElements int, _countBH int, _xmax float, _xmin float, _ymax float, _ymin float, _zmax float, _zmin float, _remnant string, _x float, _y float, _z float, join string, _length float, _issues{}.count string, _issues{}.issue_found string, _issues{}.location_sample.x string, _issues{}.location_sample.y string, _issues{}.location_sample.z string, BH_ID select string, Layer ID select string, Coordinate X select string, Coordinate Y select string, Coordinate Z select string, id int, Projektname string, Name öffentlich string, Restriktion string,
      Koordinate E float, Koordinate N float, Ansatzhöhe Z [müM] float, Bohrduchmesser float, Inklination float, Tiefe (MD) [m] float, Top Fels [m] float, depth_from float, depth_to float, lithology float, _countElement int

Bookmark: Duplikate kennzeichnen, Werte zählen
Counter_2
    CNT_ATTR = _countElements
    DOMAIN = counter
    SCOPE = Local
    START = 1
    -> FeatureMerger [REQUESTOR]
DuplicateFilter
    INPUT_ORDERED_CHOICE = No
    KEYATTR = BH_ID select
    UNIQUE -> Counter
Counter
    CNT_ATTR = _countBH
    DOMAIN = counter
    SCOPE = Local
    START = 1
    -> AttributeKeeper
AttributeKeeper
    CREATE_BULK_MODE_FEATURES = NO
    KEEP_ATTRS = _countBH,BH_ID select
    -> FeatureMerger [SUPPLIER]
FeatureMerger
    ATTR_ACCUM_MODE = Merge Supplier
    ATTR_CONFLICT_RES = Use Requestor
    IGNORE_NULLS = No
    JOIN_KEYS = @Value(BH_ID select) @Value(BH_ID select) AUTO
    MERGE_TYPE = Attributes Only
    PROCESS_DUPS = NO
    REJECT_NULL_MISSING_KEYS = No
    SUPPLIERS_FIRST = No
    MERGED -> Tester_2
    MERGED -> FeatureMerger_3 [SUPPLIER]

Bookmark: Line Segment of 2 vertices test
VertexCounter
    CNT_ATTR = _coordcount
    -> Tester
Note: Falls Objekt nur 1 Vertex: failed
Tester
    BOOL_OP = OR
    COMPOSITE_TEST = 1
    TEST_CLAUSE = TEST @Value(_coordcount) != 1
    TEST_MODE = TEST
    PASSED -> AttributeRemover
AttributeRemover
    REMOVE_ATTRS = _coordcount
    -> GeometryFilter_3
GeometryFilter_3
    BREAK_AGG = No
    GEOM_PORT_NAMES = Area Text Ellipse Raster Instance Line Surface Arc "Point Cloud" Null Collection Point Solid
    LINE -> BoundsExtractor

Bookmark: Filtering inclined boreholes
Note: min and max values of coordinates get extracted
BoundsExtractor
    XMAX = _xmax
    XMIN = _xmin
    YMAX = _ymax
    YMIN = _ymin
    ZMAX = _zmax
    ZMIN = _zmin
    -> TestFilter
    -> FeatureMerger_2 [REQUESTOR]
TestFilter
    DEFAULT_VALUE = Inclined_segment
    TEST_LIST:
      "BOOL_OP,OR,COMPOSITE_TEST,""""""1 OR 2"""""",TEST_CLAUSE,TEST @Value(_xmin) = @Value(_xmax)
      TEST @Value(_ymin) = @Value(_ymax)",Vertical_segment
    Inclined_segment -> DuplicateFilter_2
DuplicateFilter_2
    INPUT_ORDERED_CHOICE = No
    KEYATTR = _countBH
    UNIQUE -> AttributeKeeper_4
AttributeKeeper_4
    CREATE_BULK_MODE_FEATURES = NO
    KEEP_ATTRS = _countBH
    -> AttributeCreator
AttributeCreator
    ATTR_TABLE = SET_TO BH_Type = Inclined
    -> FeatureMerger_2 [SUPPLIER]
FeatureMerger_2
    ATTR_ACCUM_MODE = Merge Supplier
    ATTR_CONFLICT_RES = Use Requestor
    IGNORE_NULLS = No
    JOIN_KEYS = @Value(_countBH) @Value(_countBH) AUTO
    MERGE_TYPE = Attributes Only
    PROCESS_DUPS = NO
    REJECT_NULL_MISSING_KEYS = No
    SUPPLIERS_FIRST = No
    MERGED -> CoordinateSwapper
    MERGED -> LengthCalculator
    UNMERGED_REQUESTOR -> AttributeCreator_2

Bookmark: Vertical Boreholes: Schichtdaten werden vertikal zu 3D Segmenten mit BH_Radius als Dicke und z als Tiefe
AttributeCreator_2
    ATTR_TABLE = SET_TO BH_Type = Vertical
    -> PipeReplacer
PipeReplacer
    OUTER_RADIUS = @Value(BH_Radius)
    -> FeatureMerger_3 [REQUESTOR]
Note: lines get chopped
Chopper_2
    DEAGGREGATE_INPUT = Deaggregate
    MAX_VERTICES = 1
    MODE = By Vertex
    REMNANT_ATTR = _remnant
    CHOPPED -> CoordinateExtractor_2
CoordinateExtractor_2
    IND = 0
    MODE = Specify Coordinate
    X_ATTR = _x
    Y_ATTR = _y
    Z_ATTR = _z
    -> Sorter_2
Sorter_2
    SORT_PARM = _countBH NUMERIC ASCENDING _countElements NUMERIC ASCENDING _z NUMERIC DESCENDING
    SORTED -> Tester_3
Note: Daten von Top layer werden weiterverwendet
Tester_3
    BOOL_OP = OR
    COMPOSITE_TEST = 1
    TEST_CLAUSE = TEST @Value(_zmax) = @Value(_z)
    TEST_MODE = TEST
    PASSED -> Bufferer_3
Bufferer_3
    ANGLE = 22.5
    CAP_STYLE = Round
    CORNER_STYLE = Round
    MODE = AREA
    OFFSET = @Value(BH_Radius)
    OFFSET_UNITS = NONE
    BUFFERED -> 3DForcer_2
3DForcer_2
    KEEPZVAL = No
    ZVALATTR = @Value(_z)
    -> Extruder_2
Note: negative value delta-z gets extruded from top to base of layer
Extruder_2
    DIRECTION = Vertical
    DISTANCE = -(@Value(_zmax)-@Value(_zmin))
    EXTRUDED -> Tester_8
    EXTRUDED -> FeatureMerger_3 [REQUESTOR]

Bookmark: Inclined Boreholes
CoordinateSwapper
    SWAP_TYPE = X <-> Z
    -> LineCombiner
Note: Layers from same borehole on yz plane are combined
LineCombiner
    ACCUM_ATTRS_NAME = Use Attributes From One Feature
    BREAK = no
    BREAK_CONNECTION_ATTRIBUTES = _countBH
    CONNECT_Z_MODE = Ignore
    CONSIDER_NODE_ELEVATION = no
    DEAGGREGATE_GEOMETRY = Deaggregate
    JUNCTIONS_IGNORE_ATTRIBUTES = No
    LINES_AS_SEGMENTS = No
    PRESERVE = no
    TOPOLOGY = End noded
    LINE -> CoordinateSwapper_2
CoordinateSwapper_2
    SWAP_TYPE = X <-> Z
    -> Bufferer
Note: yz plane and whole boreholes
Bufferer
    MODE = SOLID
    OFFSET = @Value(BH_Radius)
    SPHERE_DIVISIONS = 2
    BUFFERED -> AttributeRemover_2
AttributeRemover_2
    REMOVE_ATTRS = _countElements
    -> GeometryFilter_2
GeometryFilter_2
    BREAK_AGG = No
    GEOM_PORT_NAMES = Point Line Arc Area Ellipse Text Raster "Point Cloud" Surface Solid Collection Null Instance
    SOLID -> GeometryValidator
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> AttributeCreator_11
    REPAIRED -> AttributeCreator_11
AttributeCreator_11
    ATTR_TABLE = SET_TO join = 1
    -> FeatureMerger_4 [SUPPLIER]
LengthCalculator
    DIM = 2
    LEN_ATTR = _length
    MULT = 1
    -> Chopper
Chopper
    DEAGGREGATE_INPUT = Deaggregate
    MAX_VERTICES = 1
    MODE = By Vertex
    REMNANT_ATTR = _remnant
    CHOPPED -> CoordinateExtractor
CoordinateExtractor
    IND = 0
    MODE = Specify Coordinate
    X_ATTR = _x
    Y_ATTR = _y
    Z_ATTR = _z
    -> Sorter
Note: xz plane and segments
Sorter
    SORT_PARM = _countBH NUMERIC ASCENDING _countElements NUMERIC ASCENDING _z NUMERIC DESCENDING
    SORTED -> Tester_4
Tester_4
    BOOL_OP = OR
    COMPOSITE_TEST = 1
    TEST_CLAUSE = TEST @Value(_zmax) = @Value(_z)
    TEST_MODE = TEST
    PASSED -> Bufferer_2
Note: buffered with / 20+(lenght*2)
Bufferer_2
    ANGLE = 22.5
    CAP_STYLE = Square
    CORNER_STYLE = Miter
    MITER_LIMIT = 1
    MODE = AREA
    OFFSET = 20+(@Value(_length)*2)
    OFFSET_UNITS = NONE
    BUFFERED -> 3DForcer
3DForcer
    KEEPZVAL = No
    ZVALATTR = @Value(_z)
    -> Extruder
Extruder
    DIRECTION = Vertical
    DISTANCE = -(@Value(_zmax)-@Value(_zmin))
    EXTRUDED -> GeometryFilter
GeometryFilter
    BREAK_AGG = No
    GEOM_PORT_NAMES = Point Line Arc Area Ellipse Text Raster "Point Cloud" Surface Solid Collection Null Instance
    SOLID -> GeometryCoercer_2
Note: warum dieser hier nötig?
GeometryCoercer_2
    GQUERY:
      for $geom in //geometry
      where $geom/count(parent::geometry) = 0
      return number($geom/@fme_id)
    KIND = fme_brep_solid
    COERCED -> GeometryValidator_3
GeometryValidator_3
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> AttributeCreator_7
    REPAIRED -> AttributeCreator_7
AttributeCreator_7
    ATTR_TABLE = SET_TO join = 1
    -> GeometryRemover
    -> CSGBuilder [B]
GeometryRemover
    -> FeatureMerger_4 [REQUESTOR]
FeatureMerger_4
    JOIN_KEYS = @Value(_countBH) @Value(_countBH) AUTO
    MERGE_TYPE = Geometry
    PROCESS_DUPS = NO
    REJECT_NULL_MISSING_KEYS = No
    SUPPLIERS_FIRST = No
    MERGED -> CSGBuilder [A]
Note: common portion of two objects / A based on radius / B bigger than radius
CSGBuilder
    GROUP_BY = _countElements
    INTERSECTION -> FeatureMerger_3 [REQUESTOR]

Bookmark: New Bookmark
GeometryRemover_2
    -> AttributeKeeper_2
AttributeKeeper_2
    CREATE_BULK_MODE_FEATURES = NO
    KEEP_ATTRS = fme_color,_countElement
    -> AppearanceStyler_2
AppearanceStyler_2
    ALPHA = 1.0
    DIFFUSE_COLOR = @Value(fme_color)
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_2 [APPEARANCE]
AppearanceRemover_2
    SIDE_TO_REMOVE = Front and Back Sides
    -> GeometryPropertySetter_2
Note: ?
GeometryPropertySetter_2
    OVERWRITE_CHOICE = Yes
    REMOVE_ATTRIBUTE = No
    SETTYPE_PARAM = Traits From Attributes
    SRC_ATTRS = fme_color
    SET -> AppearanceSetter_2 [GEOMETRY]
AppearanceSetter_2
    DEF_STORAGE = Create New Definitions
    GQUERY:
      for $geom in //geometry
      where $geom/count(parent::geometry) = 0
      return number($geom/@fme_id)
    JOIN_ATTR = fme_color
    JOIN_TRAIT = fme_color
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> BH2_cesiumTiles_v2 (writer CESIUM3DTILES_1)
