FME workspace BH_2_CesiumTiles_070622_pipereplacer_ama.fmw

Parameters:
- BH_Diameter =
- BH_ID =
- DestDataset_CESIUM3DTILES =
- DestDataset_OBJ =
- LayerID_select =
- SourceDataset_CSV2 =
- SourceDataset_XLSXR =
- SourceDataset_XLSXR_3 =

Readers:
- CSV2_1: CSV2 from $(SourceDataset_CSV2)
- XLSXR_1: XLSXR from $(SourceDataset_XLSXR_3)
- XLSXR_2: XLSXR from $(SourceDataset_XLSXR)

Writers:
- CESIUM3DTILES_1: CESIUM3DTILES to $(DestDataset_CESIUM3DTILES) in EPSG:4326
- OBJ_1: OBJ to $(DestDataset_OBJ)

Note: Swissforage_Export_Dez21
Sheet1 (reader XLSXR_1)
    attributes: SHORTNAME char(7), ORIGNAME char(47), Projektname char(140), NAMEPUB char(54), BOHRTYP char(2), RESTRICTIO char(2), Restriktion Datum char(11), SRS number(9,0), QC Koordinaten number(9,0), HRS number(9,0), QC Ansatz Z number(9,0), Landnutzung string, Kanton char(12), Gemeinde char(19), Strasse string, Bohrmethode number(9,0), BOHREDAT char(11), Bohrgut number(9,0), GRUND char(5), Bohrduchmesser number(5,0), Status Bohrloch number(9,0), Inklination number(5,1), Einfallsrichtung number(6,0), QC Inc/Richtung number(8,0), TIEFEMD number(7,2), QC Tiefe number(9,0), Top Fels [m] number(9,2), QC Top Fels number(9,0), Grundwasser char(6), stratigraphy_id number(4,0),
      stratigraphy_name char(37), DEPTHFROM number(7,2), DEPTHTO number(7,2), LAYERDESC char(12806), ORIGGEOL char(254), qt_description number(5,0), LITHOLOGY number(9,0), LITHOSTRAT number(9,0), CHRONOSTR number(9,0), TECTO string, symbol string, color number(18,0), plasticity date, humidity date, consistance number(9,0), alteration string, compactness string, jointing string, soil_state number(9,0), organic_component string, striae boolean, grain_size_1 string, grain_size_2 string, grain_shape string, grain_granularity string, further_properties string, USCS1 string, USCS100 string, USCS3 string, uscs_original string,
      uscs_determination string, unconrocks string, debris string, lit_pet_deb string, lithok string, kirost string, notes char(256), Eindeutige ID string, CH string, InfoGeol string, Original ID string, geoquat string, geomol string, geotherm string, kantons ID string, test string, geometry string, XCOORD x_coordinate, YCOORD y_coordinate, ZCOORDB z_coordinate
    -> AttributeKeeper_5
test_rheinau (reader XLSXR_2)
    attributes: id number(3,0), Originalname char(27), Projektname char(115), Name öffentlich char(27), Bohrtyp date, Restriktion date, Restriktion Datum string, Koordinate E number(12,3), Koordinate N number(12,3), SRS number(9,0), QC Koordinaten number(9,0), HRS number(9,0), QC Ansatz Z number(9,0), Landnutzung string, Kanton char(13), Gemeinde char(10), Strasse string, Bohrmethode number(9,0), Bohrende Datum date, Bohrgut number(9,0), Bohrzweck number(9,0), Bohrduchmesser string, Status Bohrloch number(9,0), TAN Inklination number(31,18), TAN Einfallsrichtung number(19,15), QC Inc/Richtung number(8,0), Tiefe (MD) [m] number(6,1), Endteufe (TVD) number(9,5), X Offset number(31,15), Y Offset number(31,15),
      XCOORD number(12,3), YCOORD number(12,3), QC Tiefe number(9,0), Top Fels [m] number(3,0), QC Top Fels number(9,0), Grundwasser string, stratigraphy_id number(3,0), stratigraphy_name char(19), depth_from number(6,1), depth_to number(9,5), description char(202), geology string, qt_description number(5,0), lithology number(9,0), lithostratigraphy number(9,0), chronostratigraphy date, tectonic_unit string, symbol string, color string, plasticity date, humidity date, consistance number(9,0), alteration string, compactness string, jointing string, soil_state number(9,0), organic_component string, striae string, grain_size_1 string, grain_size_2 string,
      grain_shape string, grain_granularity string, further_properties string, uscs_1 string, uscs_2 string, uscs_3 string, uscs_original string, uscs_determination string, unconrocks string, debris string, lit_pet_deb string, lithok string, kirost string, notes char(256), Eindeutige ID string, CH string, InfoGeol string, Original ID string, geoquat string, geomol string, geotherm string, kantons ID string, test string, delta X Offset x_coordinate, delta Y Offset y_coordinate, Ansatzhöhe Z [müM] z_coordinate
    -> AttributeKeeper_6
Note: Geodin
Export (reader XLSXR_1)
    attributes: LONGNAME char(255), ZCOORDE char(255), SHORTNAME char(255), PROJEKTNAM char(255), ORIGNAME char(255), BOHRTYP char(255), NAMEPUB char(255), QCCOORDEN char(255), QCELEVATIZ char(255), TIEFEMD char(255), QCTIEFE char(255), BOHREDAT char(255), LAND char(255), KANTON char(255), GEMEINDE char(255), STRASSE char(255), RESTRICTIO char(255), RESTRICDAT char(255), BMETHOD char(255), BOHRGUT char(255), BOHRZWECK char(255), STATUSBOHR char(255), TOPBEDROCK char(255), QCTOPBED char(255), GROUNDWATE char(255), DIAMETER char(255), INKLINAT char(255), RICHTUNG char(255), QCINKRICHT char(255), LITTOPBED char(255),
      STRATOPDEB char(255), CHROTOPBED char(255), EPSG char(255), HRS char(255), ARTANSATZZ char(255), LANDNUTZNG char(255), BEARBSTATU char(255), GEOLDATBED char(255), ATTRIBEARB char(255), ANZSCHICHT char(255), BEMERKUNG char(255), FEHLER char(255), LETZTBEARB char(255), BEARBDATUM char(255), GEODINGUID_STGENER char(255), INTV char(255), INTART char(255), GRUND char(255), QCBOHRUNG char(255), LETZTBEARB_1 char(255), BEARBDATUM_1 char(255), BAUGRDKLAS char(255), GEODINGUID_STLYRTIT char(255), DEPTHFROM char(255), DEPTHTO char(255), LAYERDESC char(255), DESCRIPTIO char(255), BESCHRSTAN char(255), QCBESCHR char(255), LITHOLOGY char(255),
      LITHOSTRAT char(255), CHRONOSTR char(255), TECTO char(255), COLOUR char(255), HUMIDITY char(255), PLASTICITY char(255), CONSISTENC char(255), COMPACTNES char(255), SOILSTATE char(255), ALTERATION char(255), GRADUATION char(255), ORGANICOMP char(255), STRIAE char(255), GRAINSIZE1 char(255), GRAINSHAPE char(255), GRAINSIZE2 char(255), COHESION char(255), USCS1 char(255), USCS2 char(255), USCS3 char(255), USCSBEST char(255), GROBBESTAN char(255), LITPETGROB char(255), CLASSDESOL char(255), PROCESSOR char(255), DATEPRO char(255), KORNRUNDU char(255), BOHRENDTIE char(255), LITHOK char(255), KIROST char(255),
      ADDPROPS char(255), KLUEFTUNG char(255), USCSORIGIN char(255), INTART_1 char(255), INTKLASSE char(255), COMMENTARY char(255), ORIGGEOL char(255), LAGEOQID char(255), LETZTBEARB_2 char(255), BEARBDATUM_2 char(255), GEODINGUID_STLAYER char(255), XCOORD char(255), YCOORD char(255), ZCOORDB char(255)
    -> AttributeKeeper_5
Note: überprüfen: mapping von SF script hier bereits vollständig enthalten?
AttributeKeeper_5
    CREATE_BULK_MODE_FEATURES = NO
    KEEP_ATTRS = DEPTHFROM,DEPTHTO,DIAMETER,LITHOLOGY,RESTRICTIO,SHORTNAME,TOPBEDROCK,XCOORD,YCOORD,ZCOORDB,INKLINAT,NAMEPUB,PROJEKTNAM,TIEFEMD
    -> AttributeRenamer_2
AttributeRenamer_2
    ATTR_TABLE:
      RENAME_SET_DEFAULT SHORTNAME > id
      RENAME_SET_DEFAULT PROJEKTNAM > Projektname
      RENAME_SET_DEFAULT NAMEPUB > Name öffentlich
      RENAME_SET_DEFAULT RESTRICTIO > Restriktion
      RENAME_SET_DEFAULT TOPBEDROCK > Top Fels [m]
      RENAME_SET_DEFAULT DIAMETER > Bohrduchmesser
      RENAME_SET_DEFAULT INKLINAT > Inklination
      RENAME_SET_DEFAULT DEPTHFROM > depth_from
      RENAME_SET_DEFAULT DEPTHTO > depth_to
      RENAME_SET_DEFAULT LITHOLOGY > lithology
      RENAME_SET_DEFAULT XCOORD > Koordinate E
      RENAME_SET_DEFAULT YCOORD > Koordinate N
      RENAME_SET_DEFAULT ZCOORDB > Ansatzhöhe Z [müM]
      RENAME_SET_DEFAULT TIEFEMD > Tiefe (MD) [m]
    MISSING_INPUT_ATTRS = REMOVE
    -> AttributeCreator_6 [off]
    -> AttributeCreator_3 [off]
Note: Export Swissforage
CSV (reader CSV2_1)
    attributes: id uint32, Originalname varchar(74), Projektname varchar(251), Name öffentlich varchar(74), Bohrtyp date, Restriktion date, Restriktion Datum varchar(11), Koordinate E real64, Koordinate N real64, SRS date, QC Koordinaten date, Ansatzhöhe Z [müM] real32, HRS date, QC Ansatz Z date, Landnutzung date, Kanton varchar(13), Gemeinde varchar(24), Strasse varchar(30), Bohrmethode date, Bohrende Datum varchar(11), Bohrgut date, Bohrzweck date, Bohrduchmesser real32, Status Bohrloch date, Inklination real32, Einfallsrichtung real32, QC Inc/Richtung uint32, Tiefe (MD) [m] real32, QC Tiefe date, Top Fels [m] real32,
      QC Top Fels date, Grundwasser varchar(6), stratigraphy_id uint32, stratigraphy_name varchar(44), depth_from real32, depth_to real32, description varchar(12806), geology varchar(254), qt_description uint32, lithology real64, lithostratigraphy real64, chronostratigraphy date, tectonic_unit varchar(1), symbol varchar(1), color varchar(63), plasticity date, humidity date, consistance date, alteration date, compactness date, jointing varchar(1), soil_state date, organic_component real64, striae varchar(6), grain_size_1 date, grain_size_2 date, grain_shape varchar(1), grain_granularity varchar(27), further_properties date, uscs_1 date,
      uscs_2 date, uscs_3 varchar(1), uscs_original varchar(1), uscs_determination date, unconrocks varchar(1), debris uint32, lit_pet_deb varchar(1), lithok varchar(1), kirost varchar(1), notes varchar(9782), Eindeutige ID varchar(1), CH varchar(1), InfoGeol varchar(1), Original ID varchar(1), geoquat varchar(1), geomol varchar(1), geotherm varchar(1), kantons ID varchar(1), test varchar(1)
    -> Tester
Tester
    BOOL_OP = OR
    COMPOSITE_TEST = 1
    TEST_CLAUSE = TEST @Value(id) = 34
    TEST_MODE = TEST
    PASSED -> AttributeKeeper_6 [off]
AttributeKeeper_6
    CREATE_BULK_MODE_FEATURES = NO
    KEEP_ATTRS = Bohrduchmesser,depth_from,depth_to,id,Restriktion,Top Fels [m],Koordinate E,Koordinate N,lithology,Name öffentlich,Projektname,Ansatzhöhe Z [müM],Tiefe (MD) [m]
    -> AttributeCreator_6
    -> AttributeCreator_3
Sorter_5
    GROUP_BY = "BH_ID select"
    SORT_PARM = depth_from NUMERIC DESCENDING
    SORTED -> FeatureMerger_5 [REQUESTOR]
File1 (writer OBJ_1)
BH2_cesiumTiles_v2 (writer CESIUM3DTILES_1)
    attributes: Solid_Unconsolidated string, BH_ID select string, Layer ID select string, id int, Projektname string, Name öffentlich string, Restriktion string, Koordinate E float, Koordinate N float, Ansatzhöhe Z [müM] float, Bohrduchmesser float, Tiefe (MD) [m] float, Top Fels [m] float, depth_from float, depth_to float, lithology float, Inklination string, BH_Geometry_X float, BH_Geometry_Y float, BH_Geometry_Z string, xgeom float, ygeom float, zgeom string, _countElement int, fme_rejection_code string

Bookmark: input interval table
AttributeCreator_3
    ATTR_TABLE:
      SET_TO BH_ID select = $(BH_ID)
      SET_TO Layer ID select = $(LayerID_select)
    -> Sorter_5

Bookmark: Input geometry xyz table
AttributeCreator_6
    ATTR_TABLE:
      SET_TO xgeom = @Value(Koordinate E)
      SET_TO ygeom = @Value(Koordinate N)
      SET_TO zgeom = @Evaluate(@Value(Ansatzhöhe Z [müM])-@Value(depth_from))
    -> AttributeKeeper_7
AttributeKeeper_7
    CREATE_BULK_MODE_FEATURES = NO
    KEEP_ATTRS = id,xgeom,ygeom,zgeom,Restriktion,Top Fels [m],Ansatzhöhe Z [müM],depth_from,depth_to
    -> AttributeCreator_5

Bookmark: Input geometry
AttributeCreator_5
    ATTR_TABLE:
      SET_TO BH_ID select = $(BH_ID)
      SET_TO BH_Geometry_X = @Value(xgeom)
      SET_TO BH_Geometry_Y = @Value(ygeom)
      SET_TO BH_Geometry_Z = @Value(zgeom)
    -> Sorter_4

Bookmark: Build line for every borehole id
Note: Sorted from base to top
Sorter_4
    SORT_PARM = BH_Geometry_Z NUMERIC DESCENDING
    SORTED -> VertexCreator_3
Note: A vertex is built at every coordinate
VertexCreator_3
    MEASURE_TYPE = Continuous
    MODE_NAME = Replace with Point
    XVAL = @Value(BH_Geometry_X)
    YVAL = @Value(BH_Geometry_Y)
    ZVAL = @Value(BH_Geometry_Z)
    -> CoordinateSwapper_3 [off]
    -> VertexCreator_4
Note: Only usefull for swissforage export (layers), not for drillpath (paths)
VertexCreator_4
    IGNORE_DUPLICATES = No
    MEASURE_TYPE = Continuous
    MISSING_VAL_MODE = Compute
    MODE_NAME = Add Point
    XVAL = @Value(BH_Geometry_X)
    YVAL = @Value(BH_Geometry_Y)
    ZVAL = @Evaluate(@Value(Ansatzhöhe Z [müM])-@Value(depth_to))
    -> CoordinateSwapper_3
CoordinateSwapper_3
    SWAP_TYPE = X <-> Z
    -> LineBuilder_2
LineBuilder_2
    ACCUM_INPUT_ATTRS = Use Attributes From One Feature
    GROUP_BY = "BH_ID select"
    REMOVE_DUPLICATES = No
    LINE -> CoordinateSwapper_4
CoordinateSwapper_4
    SWAP_TYPE = X <-> Z
    -> FeatureMerger_5 [SUPPLIER]

Bookmark: Build pipe segments
FeatureMerger_5
    ATTR_ACCUM_MODE = Merge Supplier
    ATTR_CONFLICT_RES = Use Requestor
    IGNORE_NULLS = No
    JOIN_KEYS = @Value(BH_ID select) @Value(BH_ID select) AUTO
    MERGE_TYPE = Attributes and Geometry
    PROCESS_DUPS = NO
    REJECT_NULL_MISSING_KEYS = No
    SUPPLIERS_FIRST = No
    MERGED -> Snipper_2
Note: Boreholes are cut into layer segments
Snipper_2
    DEAGGREGATE_INPUT = YES
    ENDLOCATIONATTR = @Value(depth_to)
    MEASUREMENTTYPE = 3D
    SNIPMODE = Distance (Value)
    STARTLOCATIONATTR = @Value(depth_from)
    -> PipeReplacer_3
PipeReplacer_3
    OUTER_RADIUS = $(BH_Diameter)
    -> AttributeCreator

Bookmark: Select color attribute
AttributeCreator
    ATTR_TABLE = SET_TO Solid_Unconsolidated = FME_CONDITIONAL:DEFAULT_VALUE'Unconsolidated'BOOL_OP;OR;COMPOSITE_TEST;1;TEST @Value(depth_from) >= @Value(Top Fels [m])'Solid'FME_NUM_CONDITIONS2___
    -> FeatureColorSetter
FeatureColorSetter
    MODE = Random
    RANDOM_COLOR_CAP = 0
    RANDOM_MODE = Attributes
    COLORED -> Counter_3
Counter_3
    CNT_ATTR = _countElement
    DOMAIN = counter
    SCOPE = Local
    START = 1
    -> CoordinateSystemSetter_2
CoordinateSystemSetter_2
    COORDSYS = CH1903Plus_1.LV95/01
    -> AppearanceRemover_2
    -> GeometryRemover_2
GeometryRemover_2
    -> AttributeKeeper_2
AttributeKeeper_2
    CREATE_BULK_MODE_FEATURES = NO
    KEEP_ATTRS = fme_color,_countElement
    -> AppearanceStyler_2
AppearanceStyler_2
    ALPHA = 1.0
    DIFFUSE_COLOR = @Value(fme_color)
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter_2 [APPEARANCE]
AppearanceRemover_2
    SIDE_TO_REMOVE = Front and Back Sides
    -> GeometryPropertySetter_2
    <REJECTED> -> GeometryPropertySetter_2
GeometryPropertySetter_2
    OVERWRITE_CHOICE = Yes
    REMOVE_ATTRIBUTE = No
    SETTYPE_PARAM = Traits From Attributes
    SRC_ATTRS = fme_color
    SET -> AppearanceSetter_2 [GEOMETRY]
AppearanceSetter_2
    DEF_STORAGE = Create New Definitions
    GQUERY:
      for $geom in //geometry
      where $geom/count(parent::geometry) = 0
      return number($geom/@fme_id)
    JOIN_ATTR = fme_color
    JOIN_TRAIT = fme_color
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> BH2_cesiumTiles_v2 (writer CESIUM3DTILES_1)
    -> File1 (writer OBJ_1)
